CSource DEFINITIONS AUTOMATIC TAGS ::=

BEGIN

A ::= SEQUENCE {
    a INTEGER (-128..127),
    b INTEGER (-32768..32767),
    c INTEGER (-2147483648..2147483647),
    e INTEGER (0..255),
    f INTEGER (0..65535),
    g INTEGER (0..4294967295),
    i BOOLEAN,
    j OCTET STRING (SIZE (11))
}

END

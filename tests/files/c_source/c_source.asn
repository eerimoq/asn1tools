CSource DEFINITIONS AUTOMATIC TAGS ::=

BEGIN

IMPORTS REFERENCED-SEQUENCE, REFERENCED-ENUM, REFERENCED-INT FROM CRef;

A ::= SEQUENCE {
    a INTEGER (-128..127),
    b INTEGER (-32768..32767),
    c INTEGER (-2147483648..2147483647),
    d INTEGER (-9223372036854775808..9223372036854775807),
    e INTEGER (0..255),
    f INTEGER (0..65535),
    g INTEGER (0..4294967295),
    h INTEGER (0..18446744073709551615),
    i BOOLEAN,
    j OCTET STRING (SIZE (11))
}

B ::= CHOICE {
    a INTEGER (-128..127),
    b A,
    c NULL
}

C ::= SEQUENCE (SIZE (0..2)) OF B

D ::= SEQUENCE (SIZE (1..10)) OF SEQUENCE {
    a SEQUENCE {
        b CHOICE {
            c INTEGER (0..1),
            d BOOLEAN
        },
        e SEQUENCE (SIZE (3..4)) OF NULL,
        f NULL
    },
    g SEQUENCE {
        h ENUMERATED {
            i, j(4), k(512)
        } DEFAULT j,
        l OCTET STRING (SIZE (1..2))
    },
    m SEQUENCE {
        n BOOLEAN OPTIONAL,
        o INTEGER (-2..4) DEFAULT 3,
        p SEQUENCE {
            q OCTET STRING (SIZE (5)),
            r BOOLEAN OPTIONAL
        } OPTIONAL,
        s BOOLEAN DEFAULT FALSE
    }
}

E ::= SEQUENCE {
    a CHOICE {
        b CHOICE {
            c BOOLEAN
        }
    }
}

F ::= SEQUENCE (SIZE (1..2)) OF SEQUENCE (SIZE (1)) OF BOOLEAN

G ::= SEQUENCE {
    a BOOLEAN OPTIONAL,
    b BOOLEAN OPTIONAL,
    c BOOLEAN OPTIONAL,
    d BOOLEAN OPTIONAL,
    e BOOLEAN OPTIONAL,
    f BOOLEAN OPTIONAL,
    g BOOLEAN OPTIONAL,
    h BOOLEAN OPTIONAL,
    i BOOLEAN OPTIONAL
}

H ::= NULL

I ::= OCTET STRING (SIZE (24))

J ::= OCTET STRING (SIZE (22..23))

K ::= ENUMERATED {
    a
}

L ::= OCTET STRING (SIZE (0..500))

M ::= SEQUENCE {
    a K,
    b N
}

N ::= SEQUENCE {
    a K,
    b A,
    c O
}

O ::= SEQUENCE (SIZE (1..260)) OF BOOLEAN

P ::= SEQUENCE {
    a A,
    b M,
    c F
}

Q ::= CHOICE {
    c001 BOOLEAN,
    c002 BOOLEAN,
    c003 BOOLEAN,
    c004 BOOLEAN,
    c005 BOOLEAN,
    c006 BOOLEAN,
    c007 BOOLEAN,
    c008 BOOLEAN,
    c009 BOOLEAN,
    c010 BOOLEAN,
    c011 BOOLEAN,
    c012 BOOLEAN,
    c013 BOOLEAN,
    c014 BOOLEAN,
    c015 BOOLEAN,
    c016 BOOLEAN,
    c017 BOOLEAN,
    c018 BOOLEAN,
    c019 BOOLEAN,
    c020 BOOLEAN,
    c021 BOOLEAN,
    c022 BOOLEAN,
    c023 BOOLEAN,
    c024 BOOLEAN,
    c025 BOOLEAN,
    c026 BOOLEAN,
    c027 BOOLEAN,
    c028 BOOLEAN,
    c029 BOOLEAN,
    c030 BOOLEAN,
    c031 BOOLEAN,
    c032 BOOLEAN,
    c033 BOOLEAN,
    c034 BOOLEAN,
    c035 BOOLEAN,
    c036 BOOLEAN,
    c037 BOOLEAN,
    c038 BOOLEAN,
    c039 BOOLEAN,
    c040 BOOLEAN,
    c041 BOOLEAN,
    c042 BOOLEAN,
    c043 BOOLEAN,
    c044 BOOLEAN,
    c045 BOOLEAN,
    c046 BOOLEAN,
    c047 BOOLEAN,
    c048 BOOLEAN,
    c049 BOOLEAN,
    c050 BOOLEAN,
    c051 BOOLEAN,
    c052 BOOLEAN,
    c053 BOOLEAN,
    c054 BOOLEAN,
    c055 BOOLEAN,
    c056 BOOLEAN,
    c057 BOOLEAN,
    c058 BOOLEAN,
    c059 BOOLEAN,
    c060 BOOLEAN,
    c061 BOOLEAN,
    c062 BOOLEAN,
    c063 BOOLEAN,
    c064 BOOLEAN,
    c065 BOOLEAN,
    c066 BOOLEAN,
    c067 BOOLEAN,
    c068 BOOLEAN,
    c069 BOOLEAN,
    c070 BOOLEAN,
    c071 BOOLEAN,
    c072 BOOLEAN,
    c073 BOOLEAN,
    c074 BOOLEAN,
    c075 BOOLEAN,
    c076 BOOLEAN,
    c077 BOOLEAN,
    c078 BOOLEAN,
    c079 BOOLEAN,
    c080 BOOLEAN,
    c081 BOOLEAN,
    c082 BOOLEAN,
    c083 BOOLEAN,
    c084 BOOLEAN,
    c085 BOOLEAN,
    c086 BOOLEAN,
    c087 BOOLEAN,
    c088 BOOLEAN,
    c089 BOOLEAN,
    c090 BOOLEAN,
    c091 BOOLEAN,
    c092 BOOLEAN,
    c093 BOOLEAN,
    c094 BOOLEAN,
    c095 BOOLEAN,
    c096 BOOLEAN,
    c097 BOOLEAN,
    c098 BOOLEAN,
    c099 BOOLEAN,
    c100 BOOLEAN,
    c101 BOOLEAN,
    c102 BOOLEAN,
    c103 BOOLEAN,
    c104 BOOLEAN,
    c105 BOOLEAN,
    c106 BOOLEAN,
    c107 BOOLEAN,
    c108 BOOLEAN,
    c109 BOOLEAN,
    c110 BOOLEAN,
    c111 BOOLEAN,
    c112 BOOLEAN,
    c113 BOOLEAN,
    c114 BOOLEAN,
    c115 BOOLEAN,
    c116 BOOLEAN,
    c117 BOOLEAN,
    c118 BOOLEAN,
    c119 BOOLEAN,
    c120 BOOLEAN,
    c121 BOOLEAN,
    c122 BOOLEAN,
    c123 BOOLEAN,
    c124 BOOLEAN,
    c125 BOOLEAN,
    c126 BOOLEAN,
    c127 BOOLEAN,
    c128 BOOLEAN,
    c129 BOOLEAN,
    c130 BOOLEAN,
    c131 BOOLEAN,
    c132 BOOLEAN,
    c133 BOOLEAN,
    c134 BOOLEAN,
    c135 BOOLEAN,
    c136 BOOLEAN,
    c137 BOOLEAN,
    c138 BOOLEAN,
    c139 BOOLEAN,
    c140 BOOLEAN,
    c141 BOOLEAN,
    c142 BOOLEAN,
    c143 BOOLEAN,
    c144 BOOLEAN,
    c145 BOOLEAN,
    c146 BOOLEAN,
    c147 BOOLEAN,
    c148 BOOLEAN,
    c149 BOOLEAN,
    c150 BOOLEAN,
    c151 BOOLEAN,
    c152 BOOLEAN,
    c153 BOOLEAN,
    c154 BOOLEAN,
    c155 BOOLEAN,
    c156 BOOLEAN,
    c157 BOOLEAN,
    c158 BOOLEAN,
    c159 BOOLEAN,
    c160 BOOLEAN,
    c161 BOOLEAN,
    c162 BOOLEAN,
    c163 BOOLEAN,
    c164 BOOLEAN,
    c165 BOOLEAN,
    c166 BOOLEAN,
    c167 BOOLEAN,
    c168 BOOLEAN,
    c169 BOOLEAN,
    c170 BOOLEAN,
    c171 BOOLEAN,
    c172 BOOLEAN,
    c173 BOOLEAN,
    c174 BOOLEAN,
    c175 BOOLEAN,
    c176 BOOLEAN,
    c177 BOOLEAN,
    c178 BOOLEAN,
    c179 BOOLEAN,
    c180 BOOLEAN,
    c181 BOOLEAN,
    c182 BOOLEAN,
    c183 BOOLEAN,
    c184 BOOLEAN,
    c185 BOOLEAN,
    c186 BOOLEAN,
    c187 BOOLEAN,
    c188 BOOLEAN,
    c189 BOOLEAN,
    c190 BOOLEAN,
    c191 BOOLEAN,
    c192 BOOLEAN,
    c193 BOOLEAN,
    c194 BOOLEAN,
    c195 BOOLEAN,
    c196 BOOLEAN,
    c197 BOOLEAN,
    c198 BOOLEAN,
    c199 BOOLEAN,
    c200 BOOLEAN,
    c201 BOOLEAN,
    c202 BOOLEAN,
    c203 BOOLEAN,
    c204 BOOLEAN,
    c205 BOOLEAN,
    c206 BOOLEAN,
    c207 BOOLEAN,
    c208 BOOLEAN,
    c209 BOOLEAN,
    c210 BOOLEAN,
    c211 BOOLEAN,
    c212 BOOLEAN,
    c213 BOOLEAN,
    c214 BOOLEAN,
    c215 BOOLEAN,
    c216 BOOLEAN,
    c217 BOOLEAN,
    c218 BOOLEAN,
    c219 BOOLEAN,
    c220 BOOLEAN,
    c221 BOOLEAN,
    c222 BOOLEAN,
    c223 BOOLEAN,
    c224 BOOLEAN,
    c225 BOOLEAN,
    c226 BOOLEAN,
    c227 BOOLEAN,
    c228 BOOLEAN,
    c229 BOOLEAN,
    c230 BOOLEAN,
    c231 BOOLEAN,
    c232 BOOLEAN,
    c233 BOOLEAN,
    c234 BOOLEAN,
    c235 BOOLEAN,
    c236 BOOLEAN,
    c237 BOOLEAN,
    c238 BOOLEAN,
    c239 BOOLEAN,
    c240 BOOLEAN,
    c241 BOOLEAN,
    c242 BOOLEAN,
    c243 BOOLEAN,
    c244 BOOLEAN,
    c245 BOOLEAN,
    c246 BOOLEAN,
    c247 BOOLEAN,
    c248 BOOLEAN,
    c249 BOOLEAN,
    c250 BOOLEAN,
    c251 BOOLEAN,
    c252 BOOLEAN,
    c253 BOOLEAN,
    c254 BOOLEAN,
    c255 BOOLEAN,
    c256 BOOLEAN,
    c257 BOOLEAN
}

-- 1 bit signed
R ::= INTEGER (-1..0)

-- 2 bits signed
S ::= INTEGER (-2..1)

T ::= INTEGER (-1..2)

-- 7 bits signed
U ::= INTEGER (-64..63)

-- 8 bits signed
V ::= INTEGER (-128..127)

-- 9 bits signed
W ::= INTEGER (-1..510)

-- 10 bits signed
X ::= INTEGER (-2..510)

-- 10 bits unsigned
Y ::= INTEGER (10000..10512)

Z ::= BOOLEAN

-- Parameterization
AA {Param1, Param2} ::= SEQUENCE {
    a Param1,
    b Param2
}

AB ::= AA { R, Y }

AC ::= AA { Q, D }

-- All encoded values valid (1 bit).
AD ::= ENUMERATED {
    a,
    b
}

-- Extensibility - with additionals
AE ::= SEQUENCE {
    a BOOLEAN OPTIONAL,
    b BOOLEAN DEFAULT TRUE,
    c BOOLEAN,
    ...
}

AF ::= SEQUENCE {
    a BOOLEAN,
    ...,
    b AH,
    e INTEGER(0..255),
    f INTEGER(0..255),
    g INTEGER(0..255),
    h INTEGER(0..255),
    i INTEGER(0..255),
    j INTEGER(0..255) OPTIONAL,
    k INTEGER(0..255) DEFAULT 24,
    l INTEGER(0..255),
    ...
}

AG ::= SEQUENCE {
    a BOOLEAN,
    ...,
    b OCTET STRING (SIZE(0..10)),
    c SEQUENCE (SIZE (1..10)) OF BOOLEAN,
    d ENUMERATED {
        e, f(256), g(65536)
    },
    h NULL,
    i REAL (WITH COMPONENTS {
                     mantissa (-16777215..16777215),
                     base (2),
                     exponent (-149..104)
                 }),
    j CHOICE {
        k INTEGER (0..65535),
        l BOOLEAN
    },
    m OCTET STRING(SIZE(5)),
    ...
}

AH ::= SEQUENCE {
    c BOOLEAN,
    ...,
    d INTEGER(0..255),
    e ENUMERATED {f, g, h},
    ...
}

AI ::= SEQUENCE {
    a AK
}

AJ ::= SEQUENCE {
    a ENUMERATED {
        a-1, a-2
    }
}

AK ::= CHOICE {
    a AJ
}

AL ::= INTEGER (-129..127)

AM ::= INTEGER (-2..128)

AN ::= ENUMERATED { a(-16777216), b(-8388608), c(-65536), d(-32768), e(-128),
                    f(0), g(127), h(128), i(32767), j(65536), k(16777216) }

ao-value-b INTEGER ::= 1
AO ::= SEQUENCE {
    a BIT STRING { a(0), b(ao-value-b), c(7) } (SIZE(8)),
    b BIT STRING { a(0), b(1), c(23) } (SIZE(24)),
    c BIT STRING (SIZE(4)),
    d BIT STRING { a(1), b(2), c(31) } (SIZE(32)),
    e BIT STRING { a(1), b(32), c(63) } (SIZE(64))
}

AP ::= SEQUENCE {
    b REFERENCED-SEQUENCE,
    c REFERENCED-ENUM DEFAULT a,
    d REFERENCED-INT DEFAULT 1
}

AQ ::= INTEGER (0..16777215)

AR ::= SEQUENCE {
    a OCTET STRING(SIZE(0..10)) DEFAULT 'ABCD'H
}

AS ::= SEQUENCE {
    a-a BOOLEAN OPTIONAL,
    a-b CHOICE {
        b-a BOOLEAN,
        b-b BOOLEAN
    },
    a-c BOOLEAN DEFAULT TRUE
}

AT ::= SEQUENCE {
    a INTEGER (0..127),
    ...,
    b SEQUENCE (SIZE(1..32)) OF A OPTIONAL,
    ...
}

END

CRef DEFINITIONS AUTOMATIC TAGS ::=
BEGIN

REFERENCED-SEQUENCE ::= SEQUENCE {
    a INTEGER (0..127)
}

REFERENCED-ENUM ::= ENUMERATED {
    a,
    b,
    c
}

REFERENCED-INT ::= INTEGER (0..255)

AT ::= BIT STRING (SIZE(2))

AU ::= SEQUENCE {
    a-a CHOICE {
        b-a ENUMERATED {a, b},
        b-b ENUMERATED {a, b}
    }
}

END

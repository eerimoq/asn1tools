Foo DEFINITIONS AUTOMATIC TAGS ::= BEGIN

    Constants ::= INTEGER  {
        min     (-1),
        max     (1),
        unknown (2)
    } (-1..2)

    A ::= Constants (min..max)

    B ::= Constants (unknown)

    -- Mix of value and named number in same constraint.
    C ::= Constants (zero..max)

    zero INTEGER ::= 0

    -- This value should not be used in the constraints above, but
    -- instead the named numbers in the type.
    min INTEGER ::= 3

END

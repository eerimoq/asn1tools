SimpleObjects DEFINITIONS AUTOMATIC TAGS ::=

BEGIN

-- The ITEM class.
ITEM ::= CLASS {
    &id          INTEGER UNIQUE,
    &MyOpenType          OPTIONAL -- An open type (type defined in objects below).
}

-- The object set containing both objects defined below.
Items ITEM ::= {
    object-0 | object-1
}

-- Type using the object set defined above. Encodes and decodes the
-- open type 'comment' as defined by 'id'
Item ::= SEQUENCE {
    id        ITEM.&id ({Items}),
    comment   ITEM.&MyOpenType ({Items}{@id}),
    value     INTEGER
}

-- Type using the object set defined above. Encodes and decodes
-- the open type 'comment' as an open type.
ItemOpenType ::= SEQUENCE {
    id        ITEM.&id,
    comment   ITEM.&MyOpenType,
    value     INTEGER
}

-- Object 0 of class ITEM.
object-0 ITEM ::= {
    &id          0,
    &MyOpenType  INTEGER
}

-- Object 1 of class ITEM.
object-1 ITEM ::= {
    &id          1,
    &MyOpenType  IA5String
}

END

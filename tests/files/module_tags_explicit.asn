ModuleTagsExplicit DEFINITIONS ::=

BEGIN

A ::= [3] INTEGER

AI ::= [3] IMPLICIT INTEGER

BA ::= [4] A

BIA ::= [4] IMPLICIT A

BIAI ::= [4] IMPLICIT AI

CBA ::= [5] BA

CBIAI ::= [5] BIAI

CIBIA ::= [5] IMPLICIT BIA

CIBIAI ::= [5] IMPLICIT BIAI

S1 ::= SEQUENCE {
    a INTEGER,
    b BOOLEAN OPTIONAL
}

S2 ::= SEQUENCE {
    a INTEGER,
    b [2] S1,
    c CHOICE {
        a BOOLEAN
    }
}

S3 ::= SEQUENCE {
    a INTEGER,
    b [2] S1,
    c [3] EXPLICIT CHOICE {
        a BOOLEAN
    }
}

S4 ::= SEQUENCE {
    a INTEGER,
    b [1] C1,
    c [2] S1,
    d CHOICE {
        a BOOLEAN
    }
}

S5 ::= SEQUENCE {
    a INTEGER,
    b S1,
    c CHOICE {
        a BOOLEAN
    }
}

S6 ::= SEQUENCE {
    a INTEGER,
    ...,
    b BOOLEAN
}

S7 ::= SEQUENCE {
    a [2] INTEGER,
    ...,
    b BOOLEAN
}

S8 ::= SEQUENCE {
    a SEQUENCE OF CHOICE {
        a INTEGER,
        b BOOLEAN
    }
}

S9 ::= SET {
    a SET OF CHOICE {
        a INTEGER,
        b BOOLEAN
    }
}

C1 ::= CHOICE {
    a [0] CHOICE {
        a [0] INTEGER
    }
}

Type1 ::= VisibleString

Type2 ::= [APPLICATION 3] IMPLICIT Type1

Type3 ::= [2] Type2

Type4 ::= [APPLICATION 7] IMPLICIT Type3

Type5 ::= [2] IMPLICIT Type2

END

Class DEFINITIONS AUTOMATIC TAGS ::=

BEGIN

-- The ITEM class.
ITEM ::= CLASS {
    &id          INTEGER UNIQUE,
    &Value,                       -- An OpenType member.
    &comment     IA5String
}

-- The object set containing two objects, 0 and 1.
Items ITEM ::= {
    { &id 0, &Value BOOLEAN, &comment "item 0" } |
    -- The open type (Value) contains a sequence that contains an open
    -- type.
    { &id 1, &Value InnerSequence, &comment "item 1" }
}

-- Type with constraints (only items in the union above
-- allowed). Encodes and decodes the open type 'value' as defined by
-- 'id'
ItemWithConstraints ::= SEQUENCE {
    id        ITEM.&id      ({Items}),
    value     ITEM.&Value   ({Items}{@id}),
    comment   ITEM.&comment ({Items}{@id}),
    extra     INTEGER
}

-- Type without constraints. Encodes and decodes the open type
-- 'value' as an open type.
ItemWithoutConstraints ::= SEQUENCE {
    id        ITEM.&id,
    value     ITEM.&Value,
    comment   ITEM.&comment,
    extra     INTEGER
}

-- The INNER-ITEM class, part of the OpenType in ITEM object 1.
INNER-ITEM ::= CLASS {
    &type          INTEGER,
    &Value                        -- An OpenType member.
}

-- The object set containing two objects, 0 and 1, of the INNER-ITEM
-- type.
InnerItems INNER-ITEM ::= {
    { &type 0, &Value INTEGER } |
    { &type 1, &Value IA5String }
}

-- myType is decoded after the open type, myValue, is found. The
-- decoding of the open type cannot be done until after myType has
-- been decoded.
InnerSequence ::= SEQUENCE {
    myValue     INNER-ITEM.&Value ({InnerItems}{@myType}),
    myType      INNER-ITEM.&type  ({InnerItems})
}

ERROR-CLASS ::= CLASS {
    &category PrintableString (SIZE(1)),
    &code INTEGER,
    &Type
} WITH SYNTAX {
    &category
    &code
    &Type
}

ErrorSet ERROR-CLASS ::= {
    { "A" 1 INTEGER } |
    { "A" 2 REAL } |
    { "B" 1 IA5String } |
    { "B" 2 GeneralString }
}

ErrorReturn ::= SEQUENCE {
    errorCategory ERROR-CLASS.&category ({ErrorSet}) OPTIONAL,
    errors SEQUENCE OF SEQUENCE {
        errorCode ERROR-CLASS.&code     ({ErrorSet}{@errorCategory}),
        errorInfo ERROR-CLASS.&Type     ({ErrorSet}{@errorCategory,@.errorCode})
    } OPTIONAL
}

END

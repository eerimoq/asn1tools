SimpleClass DEFINITIONS AUTOMATIC TAGS ::=

BEGIN

-- The ITEM class.
ITEM ::= CLASS {
    &id          INTEGER UNIQUE,
    &Value,                       -- An OpenType member.
    &comment     IA5String
}

-- The object set containing two objects, 0 and 1.
Items ITEM ::= {
    { &id 0, &Value INTEGER, &comment "item 0" } |
    { &id 1, &Value BOOLEAN, &comment "item 1" }
}

-- Type with constraints (only items in the union above
-- allowed). Encodes and decodes the open type 'value' as defined by
-- 'id'
ItemWithConstraints ::= SEQUENCE {
    id        ITEM.&id, -- ({Items}),
    value     ITEM.&Value, -- ({Items}{@id}),
    comment   ITEM.&comment, -- ({Items}{@id}),
    extra     INTEGER
}

-- Type without constraints. Encodes and decodes the open type
-- 'value' as an open type.
ItemWithoutConstraints ::= SEQUENCE {
    id        ITEM.&id,
    value     ITEM.&Value,
    comment   ITEM.&comment,
    extra     INTEGER
}

END

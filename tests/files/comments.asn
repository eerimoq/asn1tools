-- A single line comment.

-- A single line comment with end -- Foo

-- A single line comment with /* inside.

--- A single line comment starting with -.

DEFINITIONS ::= BEGIN

-- A single line comment with */ inside.

-- A single line comment with /* foo */ inside.

/* A one line comment. */

/* A multi line
   comment. */

/* Comment /* in comment. */ */

/* A -- single line comment in another comment. */

A/* First. */ ::=-- Second. --INTEGER/* Third. */
/*/*B::=BOOLEAN*/---*/C::=OCTET STRING

END

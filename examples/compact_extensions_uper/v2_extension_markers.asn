--- Second version of the Foo protocol, with extension markers.

Foo DEFINITIONS AUTOMATIC TAGS ::=

BEGIN

  State ::= ENUMERATED {
    on (0),
    off (1)
  }

  Message ::= CHOICE {
    foo Foo,
    ...,
    -- Added in version 2.
    bar Bar
  }

  Foo ::= SEQUENCE {
    a BOOLEAN,
    b INTEGER (0..127), -- Fixed range, encoded in 7 bits.
    c INTEGER (0..7),   -- Fixed range, encoded in 3 bits.
    d BOOLEAN,
    e State,
    ...,
    -- Extension in this version, version 2.
    [[
      f INTEGER (-128..127), -- Fixed range, encoded in 8 bits.
      g BOOLEAN
    ]]
  }

  Bar ::= INTEGER (0..31)

END
